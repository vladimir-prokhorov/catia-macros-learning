'================================================================================
' Принудительное переименовывание подсборок и деталей в дереве построения.
'================================================================================
Language = "VBSCRIPT"
Sub CATMain()
	CATIA.DisplayFileAlerts = False
	Set mainDocument = CATIA.ActiveDocument
	Set rootAssembly = mainDocument.Product

	clrProp rootAssembly
	Dummie = setProp(rootAssembly, 0, 0, False)
	saveDoc rootAssembly
	CATIA.DisplayFileAlerts = True
End Sub
'================================================================================
Function setProp(thisProduct, thisAsm, thisPrt, test)
	Dim currAsm, currPrt
	currAsm = thisAsm
	currPrt = thisPrt
	Set productList = thisProduct.Products
	If (thisProduct.Definition = "Fake") Then
		'Здесь что-то должно быть! Ошибка при сохранении.
	Else
		setData thisProduct, currAsm, 0, test
	End If
	For i = 1 To productList.Count
		Set thisItem = productList.Item(i)
		If (thisItem.DescriptionRef <> "True" And thisItem.Revision <> "ANY") Then
			If (thisItem.Products.Count > 0) Then
				If (thisItem.Definition = "Fake") Then
					currPrt = setProp(thisItem, thisAsm, currPrt, test)
				Else
					currAsm = currAsm + 1
					Dummie = setProp(thisItem, currAsm, 0, test)
				End If
			Else
				currPrt = currPrt + 1
				setData thisItem, thisAsm, currPrt, test
			End If
		End If
	Next
	If (test) Then
		MsgBox "i = " & i & vbCrLf & "thisAsm = " & thisAsm & vbCrLf & "currPrt = " & currPrt
	End If
	SetProp = currPrt
End Function
'================================================================================
' Варианты запуска подпрограммы:
' 1. Сплошное переименование всех входящих сборок и деталей
'    (Примечание: Предыдущие свойства заменяются новыми)
' 2. Обновить только дату ревизии и сохранить файлы под новыми именами
' 3. Проверить соответсвие имени файла и свойств детали
'    (Пример: дата ревизии исправлена другим макросом или вручную)
'================================================================================
Sub setData(document, thisAsm, thisPrt, test)
	If (test) Then
		MsgBox "IN: " & document.PartNumber & " " & thisAsm & " " & thisPrt
	End If
	'===========================================================================
	MyVar = "Full Rename"
	If (MyVar = "Full Rename") Then
		document.PartNumber = "MP 7230 " & String(2 - Len(thisAsm), "0") & _
							thisAsm & String(2 - Len(thisPrt), "0") & thisPrt
		document.Definition = "Definition"
		document.Revision = getDate()
	End If
	If (MyVar = "Date Update") Then
		document.Revision = getDate()
	End If		
	document.DescriptionRef = "True"
	'===========================================================================
	' Выделить имя и тип файла из полного пути
	Set refProduct = document.ReferenceProduct
	Set subDocument = refProduct.Parent
	oldFullPath = subDocument.FullName
	oldFileFolder = subDocument.Path
	oldFileName = Right(oldFullPath, Len(oldFullPath) - InStrRev(oldFullPath, "\"))
	fileType = Right(oldFullPath, Len(oldFullPath) - InStrRev(oldFullPath, "."))
	'===========================================================================
	saveToRoot = True 	' Сохранить все файлы в папке основной сборки
	If (saveToRoot) Then
		sTmpPath = CATIA.ActiveDocument.Path
	Else
		sTmpPath = oldFileFolder
	End If
	newFileName = document.PartNumber & " " & document.Definition & " " & _
				  document.Revision & "." & fileType
	subDocument.SaveAs(sTmpPath & "\" & newFileName)
	'===========================================================================
	' Создаем папку для хранения устаревших данных
	Set oFileSys = CATIA.FileSystem
	sObsPath = sTmpPath + "\" + "Obsolete Data"
	sNewPath = sObsPath + "\" & oldFileName
	exists = oFileSys.FolderExists(sObsPath)
	If (Not exists) Then
		Set FoldObj = oFileSys.CreateFolder(sObsPath)
	End If
	'===========================================================================
	' Если старый файл существует, то переместь его в архив
	If (oFileSys.FileExists(oldFullPath) And oldFileName <> newFileName) Then 
		oFileSys.CopyFile oldFullPath, sNewPath, False
		oFileSys.DeleteFile oldFullPath
	End If
	'===========================================================================
	If (test) Then
		MsgBox "OUT: " & document.PartNumber & " " & thisAsm & " " & thisPrt
	End If
End Sub
'================================================================================
Function getDate()
	SetLocale "en-us"
	Dim currDay, currMonth, currYear, mark
	currDay = Day(Date)
	currMonth = Month(Date)
	currYear = Year(Date) Mod 100
	getDate = String(2 - Len(currDay), "0") & currDay & "." & _
	 		  MonthName(currMonth,true) & "." & currYear
End Function
'================================================================================
Sub clrProp(thisProduct)
	Set productList = thisProduct.Products
	For i = 1 To productList.Count
		productList.Item(i).DescriptionRef = ""
		clrProp productList.Item(i)
	Next
End Sub
'================================================================================
Sub saveDoc(thisProduct)
	thisProduct.ReferenceProduct.Parent.Save()
	Set productList = thisProduct.Products
	For i = 1 To productList.Count
		saveDoc productList.Item(i)
	Next
End Sub
'================================================================================
